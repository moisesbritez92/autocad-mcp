(defun c:AddWallDims ( / ss i ent entData p1 p2 p1x p1y p2x p2y midX midY midPt ang angPerp dimPt )
  (vl-load-com)
  (command "._LAYER" "_M" "COTAS" "_C" "1" "" "")
  (setvar "CLAYER" "COTAS")
  (setq ss (ssget "X" '((0 . "LINE"))))
  (if ss
    (progn
      (setq i 0)
      (while (< i (sslength ss))
        (setq ent (ssname ss i))
        (setq entData (entget ent))
        (setq p1 (cdr (assoc 10 entData)))
        (setq p2 (cdr (assoc 11 entData)))
        (setq p1x (car p1))
        (setq p1y (cadr p1))
        (setq p2x (car p2))
        (setq p2y (cadr p2))
        (setq midX (/ (+ p1x p2x) 2.0))
        (setq midY (/ (+ p1y p2y) 2.0))
        (setq midPt (list midX midY 0.0))
        (setq ang (angle p1 p2))
        (setq angPerp (+ ang (/ pi 2.0)))
        (setq dimPt (polar midPt angPerp 1.5))
        (if (> (distance p1 p2) 0.5)
          (command "._DIMALIGNED" p1 p2 dimPt)
        )
        (setq i (1+ i))
      )
    )
    (princ "\nNo se encontraron LINEAS.\n")
  )
  (command "._QSAVE")
  (princ)
)
