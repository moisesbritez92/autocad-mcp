(vl-load-com)

(defun oc:str-up (s)
  (strcase (vl-princ-to-string (if s s "")))
)

(defun oc:block-category (name / u)
  (setq u (oc:str-up name))
  (cond
    ((or (wcmatch u "*PUERTA*") (wcmatch u "*DOOR*")) "doors")
    ((or (wcmatch u "*VENTANA*") (wcmatch u "*WINDOW*") (wcmatch u "*WIN*")) "windows")
    ((or (wcmatch u "*MESA*") (wcmatch u "*SILLA*") (wcmatch u "*SOFA*") (wcmatch u "*BED*") (wcmatch u "*CAMA*") (wcmatch u "*TABLE*") (wcmatch u "*CHAIR*")) "furniture")
    ((or (wcmatch u "*WC*") (wcmatch u "*LAVA*") (wcmatch u "*DUCHA*") (wcmatch u "*SHOWER*")) "sanitary")
    ((or (wcmatch u "*TOMA*") (wcmatch u "*SWITCH*") (wcmatch u "*LUZ*") (wcmatch u "*LAMP*") (wcmatch u "*ELECT*")) "electrical")
    (t "raw")
  )
)

(defun oc:sanitize-name (s / out i ch)
  (setq s (vl-princ-to-string s))
  (setq out "" i 1)
  (while (<= i (strlen s))
    (setq ch (substr s i 1))
    (if (wcmatch ch "[A-Za-z0-9_-]")
      (setq out (strcat out ch))
      (setq out (strcat out "_"))
    )
    (setq i (1+ i))
  )
  out
)

(defun oc:export-block (blkName / category outpath)
  (setq category (oc:block-category blkName))
  (setq outpath (strcat "C:/Users/moise/Documents/010_MCP/blocks/" category "/" (oc:sanitize-name blkName) ".dwg"))
  (command "._-WBLOCK" outpath blkName)
  (princ (strcat "\nExported block: " blkName " -> " outpath))
)

(defun c:ExportBlocksFromPruebas (/ ss i en ed blkName seen)
  (setq seen '())
  (setq ss (ssget "X" '((0 . "INSERT"))))
  (if ss
    (progn
      (setq i 0)
      (repeat (sslength ss)
        (setq en (ssname ss i))
        (setq ed (entget en))
        (setq blkName (cdr (assoc 2 ed)))
        (if (not (member blkName seen))
          (progn
            (oc:export-block blkName)
            (setq seen (cons blkName seen))
          )
        )
        (setq i (1+ i))
      )
    )
    (princ "\nNo INSERT blocks found.")
  )
  (princ)
)
