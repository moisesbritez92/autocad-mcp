(vl-load-com)

(defun oc:str-up (s)
  (strcase (vl-princ-to-string (if s s "")))
)

(defun oc:block-category (name / u)
  (setq u (oc:str-up name))
  (cond
    ((or (wcmatch u "*PUERTA*") (wcmatch u "*DOOR*")) "doors")
    ((or (wcmatch u "*VENTANA*") (wcmatch u "*WINDOW*") (wcmatch u "*WIN*")) "windows")
    (t "other")
  )
)

(defun oc:pt2d (p)
  (list (car p) (cadr p) 0.0)
)

(defun oc:dist (a b)
  (distance (oc:pt2d a) (oc:pt2d b))
)

(defun oc:entity-center (ed / typ p1 p2 c r)
  (setq typ (cdr (assoc 0 ed)))
  (cond
    ((= typ "LINE")
      (setq p1 (cdr (assoc 10 ed)))
      (setq p2 (cdr (assoc 11 ed)))
      (list (/ (+ (car p1) (car p2)) 2.0) (/ (+ (cadr p1) (cadr p2)) 2.0) 0.0)
    )
    ((= typ "ARC") (cdr (assoc 10 ed)))
    ((= typ "CIRCLE") (cdr (assoc 10 ed)))
    ((= typ "LWPOLYLINE")
      (if (assoc 10 ed) (cdr (assoc 10 ed)) nil)
    )
    (t nil)
  )
)

(defun oc:erase-door-geometry-near (inspt / ss i en ed typ center deleted)
  (setq deleted 0)
  (setq ss (ssget "X" '((8 . "DOORS") (0 . "LINE,ARC"))))
  (if ss
    (progn
      (setq i 0)
      (repeat (sslength ss)
        (setq en (ssname ss i))
        (setq ed (entget en))
        (setq typ (cdr (assoc 0 ed)))
        (setq center (oc:entity-center ed))
        (if (and center (<= (oc:dist inspt center) 1.25))
          (progn
            (entdel en)
            (setq deleted (1+ deleted))
          )
        )
        (setq i (1+ i))
      )
    )
  )
  deleted
)

(defun oc:erase-window-geometry-near (inspt / ss i en ed typ center deleted)
  (setq deleted 0)
  (setq ss (ssget "X" '((8 . "WINDOWS") (0 . "LINE,LWPOLYLINE"))))
  (if ss
    (progn
      (setq i 0)
      (repeat (sslength ss)
        (setq en (ssname ss i))
        (setq ed (entget en))
        (setq typ (cdr (assoc 0 ed)))
        (setq center (oc:entity-center ed))
        (if (and center (<= (oc:dist inspt center) 1.50))
          (progn
            (entdel en)
            (setq deleted (1+ deleted))
          )
        )
        (setq i (1+ i))
      )
    )
  )
  deleted
)

(defun oc:apply-architecture-v2 (/ ss i en ed name inspt category deletedDoors deletedWindows deletedTotal outpath)
  (setq deletedDoors 0)
  (setq deletedWindows 0)
  (setq ss (ssget "X" '((0 . "INSERT"))))
  (if ss
    (progn
      (setq i 0)
      (repeat (sslength ss)
        (setq en (ssname ss i))
        (setq ed (entget en))
        (setq name (cdr (assoc 2 ed)))
        (setq inspt (cdr (assoc 10 ed)))
        (setq category (oc:block-category name))
        (cond
          ((= category "doors")
            (setq deletedDoors (+ deletedDoors (oc:erase-door-geometry-near inspt)))
          )
          ((= category "windows")
            (setq deletedWindows (+ deletedWindows (oc:erase-window-geometry-near inspt)))
          )
        )
        (setq i (1+ i))
      )
    )
  )
  (setq deletedTotal (+ deletedDoors deletedWindows))
  (setq outpath "C:/Users/moise/Documents/010_MCP/pruebas_reglas_v2.dwg")
  (command "._SAVEAS" "2018" outpath)
  (princ (strcat "\nArchitecture V2 applied. Deleted door entities: " (itoa deletedDoors) ", deleted window entities: " (itoa deletedWindows) ", total deleted: " (itoa deletedTotal)))
  (princ (strcat "\nSaved as: " outpath "\n"))
  (princ)
)

(defun c:ApplyArchitectureImprovementsV2 ()
  (oc:apply-architecture-v2)
)
